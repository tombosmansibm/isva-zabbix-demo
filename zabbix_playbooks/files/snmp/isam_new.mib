-- ISS-MIB { iso org(3) dod(6) internet(1) private(4) enterprises(1) 2499 }
-- Title:   IBM Security Access Manager Private Enterprise MIB
-- Version: 1.0

ISS-MIB DEFINITIONS ::= BEGIN

IMPORTS
    MODULE-IDENTITY,
    OBJECT-TYPE,
    NOTIFICATION-TYPE,
    Integer32,
    Gauge32,
    enterprises, TimeTicks
       FROM SNMPv2-SMI
    DisplayString, TruthValue, DateAndTime
       FROM SNMPv2-TC
    MODULE-COMPLIANCE, OBJECT-GROUP, NOTIFICATION-GROUP
       FROM SNMPv2-CONF
    ifAlias
       FROM IF-MIB
;

iss MODULE-IDENTITY
    LAST-UPDATED		"202111220000Z"
    ORGANIZATION		"IBM Corp."
    CONTACT-INFO		"IBM customer support: ibm.com/support"
    DESCRIPTION		"This MIB module defines SNMP trap events generated by the ISAM Appliance."
    REVISION		"202111220000Z"
    DESCRIPTION		"Updated SNMP MIB for ISAM Trap Events"
    ::= { enterprises 2499 }


-- *******************************************************************
-- High-level identifiers
-- *******************************************************************

notifications                           OBJECT IDENTIFIER ::= { iss 0 }
products                                OBJECT IDENTIFIER ::= { iss 1 }
issMIBGroups                            OBJECT IDENTIFIER ::= { iss 2 }

common                                  OBJECT IDENTIFIER ::= { products 4 }

logdata                                 OBJECT IDENTIFIER ::= { common 1 }


-- *******************************************************************
-- Groups
-- *******************************************************************
commonMIBGroups                         OBJECT IDENTIFIER ::= { issMIBGroups 4 }
notificationMIBGroups                   OBJECT IDENTIFIER ::= { issMIBGroups 5 }

-- *******************************************************************
-- Common Groups
-- *******************************************************************

logDataObjectsGroup OBJECT-GROUP
    OBJECTS {
        logEntryTime,
        logEntrySource,
        logEntryCategory,
        logEntryEventId,
        logEntryDescription,
        logEntryData
    }
    STATUS current
    DESCRIPTION "A collection of objects defining log events"
    ::= { commonMIBGroups 1 }

-- *******************************************************************
-- Log Data
-- *******************************************************************

logTable OBJECT-TYPE
    SYNTAX SEQUENCE OF LogEntry
    MAX-ACCESS not-accessible
    STATUS current
    DESCRIPTION "Log Table"
    ::= { logdata 1 }

logEntry OBJECT-TYPE
    SYNTAX LogEntry
    MAX-ACCESS not-accessible
    STATUS current
    DESCRIPTION "Log entry"
    INDEX { logEntryTime }
    ::= { logTable 1 }

LogEntry ::= SEQUENCE
{
    logEntryTime TimeTicks,
    logEntrySource DisplayString,
    logEntryCategory DisplayString,
    logEntryEventId Integer32,
    logEntryDescription DisplayString,
    logEntryData OCTET STRING
}

logEntryTime OBJECT-TYPE
    SYNTAX TimeTicks
    MAX-ACCESS read-only
    STATUS current
    DESCRIPTION "The TimeTicks when the log entry was written."
    ::= { logEntry 1 }

logEntrySource OBJECT-TYPE
    SYNTAX DisplayString
    MAX-ACCESS read-only
    STATUS current
    DESCRIPTION "The ISO 8601 date and time in UTC when the log entry was written."
    ::= { logEntry 2 }

logEntryCategory OBJECT-TYPE
    SYNTAX DisplayString
    MAX-ACCESS read-only
    STATUS current
    DESCRIPTION "The log entry event identifier."
    ::= { logEntry 3 }

logEntryEventId OBJECT-TYPE
    SYNTAX Integer32
    MAX-ACCESS read-only
    STATUS current
    DESCRIPTION "The log entry sequence number."
    ::= { logEntry 4 }

logEntryDescription OBJECT-TYPE
    SYNTAX DisplayString
    MAX-ACCESS read-only
    STATUS current
    DESCRIPTION "The log entry contents."
    ::= { logEntry 5 }

logEntryData OBJECT-TYPE
    SYNTAX OCTET STRING
    MAX-ACCESS read-only
    STATUS current
    DESCRIPTION "The source and priority of the event in format name=<source>,priority=<priority>"
    ::= { logEntry 6 }

-- *******************************************************************
-- NOTIFICATIONS
-- *******************************************************************

logdatatrap NOTIFICATION-TYPE
    OBJECTS
    {
        logEntryTime,
        logEntrySource,
        logEntryCategory,
        logEntryEventId,
        logEntryDescription,
        logEntryData
    }
    STATUS current
    DESCRIPTION
    "This trap is sent for certain types of log data.
     Only configured types of log data which will be sent as a trap."
    ::= { notifications 2 }


-- *******************************************************************
-- Notification Groups
-- *******************************************************************

logNotificationsGroup NOTIFICATION-GROUP
    NOTIFICATIONS { logdatatrap }
    STATUS current
    DESCRIPTION "Collection of log notifications"
    ::= { notificationMIBGroups 1 }

-- *******************************************************************
-- TRAPS
-- *******************************************************************

trapLogData TRAP-TYPE
    OBJECTS
    {
        logEntryTime,
        logEntrySource,
        logEntryCategory,
        logEntryEventId,
        logEntryDescription,
        logEntryData
    }
    STATUS current
    DESCRIPTION
    "This trap is sent for certain types of log data.
     Only configured types of log data which will be sent as a trap."
    ::= { notifications 2 }

END
